# robotBuilder

## #2: Support incremental construction (Functional)

### #6: Support parent-child relationships (Functional)

#### #12: Link is a valid child of a Robot (Functional)

#### #13: Joint is a valid child of a Robot (Functional)

##### #26: Parent link should be an existing Link (Functional)

##### #27: Child link should be an existing Link (Functional)

#### #14: Material is a valid child of a Robot (Functional)

#### #15: Visual is a valid child of a Link (Functional)

#### #16: Geometry is a valid child of a Visual (Functional)

#### #17: Origin is a valid child of a Visual (Functional)

#### #18: Origin is a valid child of a Joint (Functional)

#### #20: URDFTag subclass should provide a list of valid child types (Functional)

#### #21: addChild should throw an error if it cannot add a child (Functional)

#### #22: URDFTag should be able to add a child tag with unique name (Functional)

#### #24: URDFTag should be able to remove a child tag by name (Functional)

#### #25: URDFTag should be able to find a child by type or name or both (Functional)

### #7: Support reusable components (Functional)

#### #28: Link is a valid child of a Component (Functional)

#### #29: Joint is a valid child of a Component (Functional)

#### #30: All atttributes of Links and Joints within the Component can be parametrized (Functional)

##### #31: Parameter should have name (Functional)

##### #32: Parameter should have a default value (Functional)

##### #33: Parameter should have a description (Functional)

##### #34: Parameter can be attached to a node using a path (Functional)

#### #35: Component Instance should have a unique name (Functional)

##### #36: Instance Links and Joints should prefix instance name to their own names (Functional)

#### #37: Component Instance should replace all node attributes attached to parameters with specified value or default (Functional)

#### #38: Support converting selected Links and Joints into a Component (Functional)

#### #39: Component is a valid child of a Component (Functional)

## #3: Validate structure (Functional)

### #8: Each element should be a valid URDF tag or attribute (Functional)

### #9: Each element tag must have a unique name (Functional)

### #10: Element tags can have at most one parent (Functional)

### #11: Each element tag must have a type attribute (Functional)

## #4: Support import from urdf files (Functional)

## #5: Support export to urdf file (Functional)

## #19: Support all valid URDF tags (Functional)
